import FreeCAD as App
import Part

doc=App.newDocument('ReconstruccionEspacialIA')
frames=doc.addObject('App::DocumentObjectGroup','MarcosCamara')
vectors=doc.addObject('App::DocumentObjectGroup','VectoresEspaciales')
cloud=doc.addObject('App::DocumentObjectGroup','NubeDispersa')
Vector_0=doc.addObject('Part::Feature','Vector_0')
Vector_0.Shape=Part.makeLine(App.Vector(0.000000,0.000000,0.000000),App.Vector(120.000000,0.000000,0.000000))
Vector_0.addProperty('App::PropertyFloat','ConfianzaIA').ConfianzaIA=1.00000
vectors.addObject(Vector_0)
Vector_1=doc.addObject('Part::Feature','Vector_1')
Vector_1.Shape=Part.makeLine(App.Vector(0.000000,0.000000,0.000000),App.Vector(0.000000,120.000000,0.000000))
Vector_1.addProperty('App::PropertyFloat','ConfianzaIA').ConfianzaIA=1.00000
vectors.addObject(Vector_1)
Vector_2=doc.addObject('Part::Feature','Vector_2')
Vector_2.Shape=Part.makeLine(App.Vector(0.000000,0.000000,0.000000),App.Vector(0.000000,0.000000,120.000000))
Vector_2.addProperty('App::PropertyFloat','ConfianzaIA').ConfianzaIA=1.00000
vectors.addObject(Vector_2)
Vector_3=doc.addObject('Part::Feature','Vector_3')
Vector_3.Shape=Part.makeLine(App.Vector(160.000000,0.000000,15.000000),App.Vector(280.000000,0.000000,15.000000))
Vector_3.addProperty('App::PropertyFloat','ConfianzaIA').ConfianzaIA=1.00000
vectors.addObject(Vector_3)
Vector_4=doc.addObject('Part::Feature','Vector_4')
Vector_4.Shape=Part.makeLine(App.Vector(160.000000,0.000000,15.000000),App.Vector(160.000000,120.000000,15.000000))
Vector_4.addProperty('App::PropertyFloat','ConfianzaIA').ConfianzaIA=1.00000
vectors.addObject(Vector_4)
Vector_5=doc.addObject('Part::Feature','Vector_5')
Vector_5.Shape=Part.makeLine(App.Vector(160.000000,0.000000,15.000000),App.Vector(160.000000,0.000000,135.000000))
Vector_5.addProperty('App::PropertyFloat','ConfianzaIA').ConfianzaIA=1.00000
vectors.addObject(Vector_5)
Vector_6=doc.addObject('Part::Feature','Vector_6')
Vector_6.Shape=Part.makeLine(App.Vector(310.000000,35.000000,30.000000),App.Vector(429.707686,35.000000,21.629223))
Vector_6.addProperty('App::PropertyFloat','ConfianzaIA').ConfianzaIA=1.00000
vectors.addObject(Vector_6)
Vector_7=doc.addObject('Part::Feature','Vector_7')
Vector_7.Shape=Part.makeLine(App.Vector(310.000000,35.000000,30.000000),App.Vector(310.000000,155.000000,30.000000))
Vector_7.addProperty('App::PropertyFloat','ConfianzaIA').ConfianzaIA=1.00000
vectors.addObject(Vector_7)
Vector_8=doc.addObject('Part::Feature','Vector_8')
Vector_8.Shape=Part.makeLine(App.Vector(310.000000,35.000000,30.000000),App.Vector(318.370777,35.000000,149.707686))
Vector_8.addProperty('App::PropertyFloat','ConfianzaIA').ConfianzaIA=1.00000
vectors.addObject(Vector_8)
P0=doc.addObject('Part::Feature','P0')
P0.Shape=Part.makeSphere(1.5,App.Vector(-255.000000,-150.000000,1247.177600))
cloud.addObject(P0)
P1=doc.addObject('Part::Feature','P1')
P1.Shape=Part.makeSphere(1.5,App.Vector(-170.000000,-150.000000,1231.814051))
cloud.addObject(P1)
P2=doc.addObject('Part::Feature','P2')
P2.Shape=Part.makeSphere(1.5,App.Vector(-85.000000,-150.000000,1233.170580))
cloud.addObject(P2)
P3=doc.addObject('Part::Feature','P3')
P3.Shape=Part.makeSphere(1.5,App.Vector(-0.000000,-150.000000,1250.000000))
cloud.addObject(P3)
P4=doc.addObject('Part::Feature','P4')
P4.Shape=Part.makeSphere(1.5,App.Vector(85.000000,-150.000000,1266.829420))
cloud.addObject(P4)
P5=doc.addObject('Part::Feature','P5')
P5.Shape=Part.makeSphere(1.5,App.Vector(170.000000,-150.000000,1268.185949))
cloud.addObject(P5)
P6=doc.addObject('Part::Feature','P6')
P6.Shape=Part.makeSphere(1.5,App.Vector(255.000000,-150.000000,1252.822400))
cloud.addObject(P6)
P7=doc.addObject('Part::Feature','P7')
P7.Shape=Part.makeSphere(1.5,App.Vector(-255.000000,-75.000000,1247.177600))
cloud.addObject(P7)
P8=doc.addObject('Part::Feature','P8')
P8.Shape=Part.makeSphere(1.5,App.Vector(-170.000000,-75.000000,1231.814051))
cloud.addObject(P8)
P9=doc.addObject('Part::Feature','P9')
P9.Shape=Part.makeSphere(1.5,App.Vector(-85.000000,-75.000000,1233.170580))
cloud.addObject(P9)
P10=doc.addObject('Part::Feature','P10')
P10.Shape=Part.makeSphere(1.5,App.Vector(-0.000000,-75.000000,1250.000000))
cloud.addObject(P10)
P11=doc.addObject('Part::Feature','P11')
P11.Shape=Part.makeSphere(1.5,App.Vector(85.000000,-75.000000,1266.829420))
cloud.addObject(P11)
P12=doc.addObject('Part::Feature','P12')
P12.Shape=Part.makeSphere(1.5,App.Vector(170.000000,-75.000000,1268.185949))
cloud.addObject(P12)
P13=doc.addObject('Part::Feature','P13')
P13.Shape=Part.makeSphere(1.5,App.Vector(255.000000,-75.000000,1252.822400))
cloud.addObject(P13)
P14=doc.addObject('Part::Feature','P14')
P14.Shape=Part.makeSphere(1.5,App.Vector(-255.000000,-0.000000,1247.177600))
cloud.addObject(P14)
P15=doc.addObject('Part::Feature','P15')
P15.Shape=Part.makeSphere(1.5,App.Vector(-170.000000,-0.000000,1231.814051))
cloud.addObject(P15)
P16=doc.addObject('Part::Feature','P16')
P16.Shape=Part.makeSphere(1.5,App.Vector(-85.000000,-0.000000,1233.170580))
cloud.addObject(P16)
P17=doc.addObject('Part::Feature','P17')
P17.Shape=Part.makeSphere(1.5,App.Vector(-0.000000,-0.000000,1250.000000))
cloud.addObject(P17)
P18=doc.addObject('Part::Feature','P18')
P18.Shape=Part.makeSphere(1.5,App.Vector(85.000000,-0.000000,1266.829420))
cloud.addObject(P18)
P19=doc.addObject('Part::Feature','P19')
P19.Shape=Part.makeSphere(1.5,App.Vector(170.000000,-0.000000,1268.185949))
cloud.addObject(P19)
P20=doc.addObject('Part::Feature','P20')
P20.Shape=Part.makeSphere(1.5,App.Vector(255.000000,-0.000000,1252.822400))
cloud.addObject(P20)
P21=doc.addObject('Part::Feature','P21')
P21.Shape=Part.makeSphere(1.5,App.Vector(-255.000000,75.000000,1247.177600))
cloud.addObject(P21)
P22=doc.addObject('Part::Feature','P22')
P22.Shape=Part.makeSphere(1.5,App.Vector(-170.000000,75.000000,1231.814051))
cloud.addObject(P22)
P23=doc.addObject('Part::Feature','P23')
P23.Shape=Part.makeSphere(1.5,App.Vector(-85.000000,75.000000,1233.170580))
cloud.addObject(P23)
P24=doc.addObject('Part::Feature','P24')
P24.Shape=Part.makeSphere(1.5,App.Vector(-0.000000,75.000000,1250.000000))
cloud.addObject(P24)
P25=doc.addObject('Part::Feature','P25')
P25.Shape=Part.makeSphere(1.5,App.Vector(85.000000,75.000000,1266.829420))
cloud.addObject(P25)
P26=doc.addObject('Part::Feature','P26')
P26.Shape=Part.makeSphere(1.5,App.Vector(170.000000,75.000000,1268.185949))
cloud.addObject(P26)
P27=doc.addObject('Part::Feature','P27')
P27.Shape=Part.makeSphere(1.5,App.Vector(255.000000,75.000000,1252.822400))
cloud.addObject(P27)
P28=doc.addObject('Part::Feature','P28')
P28.Shape=Part.makeSphere(1.5,App.Vector(-255.000000,150.000000,1247.177600))
cloud.addObject(P28)
P29=doc.addObject('Part::Feature','P29')
P29.Shape=Part.makeSphere(1.5,App.Vector(-170.000000,150.000000,1231.814051))
cloud.addObject(P29)
P30=doc.addObject('Part::Feature','P30')
P30.Shape=Part.makeSphere(1.5,App.Vector(-85.000000,150.000000,1233.170580))
cloud.addObject(P30)
P31=doc.addObject('Part::Feature','P31')
P31.Shape=Part.makeSphere(1.5,App.Vector(-0.000000,150.000000,1250.000000))
cloud.addObject(P31)
P32=doc.addObject('Part::Feature','P32')
P32.Shape=Part.makeSphere(1.5,App.Vector(85.000000,150.000000,1266.829420))
cloud.addObject(P32)
P33=doc.addObject('Part::Feature','P33')
P33.Shape=Part.makeSphere(1.5,App.Vector(170.000000,150.000000,1268.185949))
cloud.addObject(P33)
P34=doc.addObject('Part::Feature','P34')
P34.Shape=Part.makeSphere(1.5,App.Vector(255.000000,150.000000,1252.822400))
cloud.addObject(P34)
doc.recompute()
Gui.activeDocument().activeView().viewAxonometric()
Gui.activeDocument().activeView().fitAll()
